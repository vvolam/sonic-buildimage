module sonic-smart-switch {

    yang-version 1.1;

	namespace "http://github.com/sonic-net/sonic-smart-switch";
	prefix smart-switch;

	import ietf-inet-types {
		prefix inet;
	}

	import sonic-types {
		prefix stypes;
	}

	import sonic-port {
		prefix port;
	}

	organization
		"SONiC";

	contact
		"SONiC";

	description "Smart Switch yang Module for SONiC OS";

	revision 2023-10-17 {
		description "First Revision";
	}

	revision 2025-01-11 {
		description "Add new container DPU_PORT";
	}

	container sonic-smart-switch {

		container MID_PLANE_BRIDGE {

			description "MID_PLANE_BRIDGE part of config_db.json";

			container GLOBAL {
				leaf bridge {
					type string {
						pattern "bridge-midplane";
					}
					description "Name of the midplane bridge";

					must "(current()/../ip_prefix)";
				}

				leaf ip_prefix {
					type stypes:sonic-ip4-prefix;
					description "IP prefix of the midplane bridge";
				}
			}
			/* end of container GLOBAL */
		}
		/* end of container MID_PLANE_BRIDGE */

		container DPUS {
			description "DPUS part of config_db.json";

			list DPUS_LIST {
				key "dpu_name";

				leaf dpu_name {
					description "Name of the DPU";
					type string {
						pattern "dpu[0-9]+";
					}
				}

				leaf midplane_interface {
					description "Name of the interface that represents DPU";

					type string {
						pattern "dpu[0-9]+";
					}

					must "(current() = current()/../dpu_name)";
				}
			}
			/* end of container DPUS_LIST */
		}
		/* end of container DPUS */

		container DPU_PORT {
			description "DPU_PORTs part of config_db.json";

			list DPU_PORT_LIST {
				description "Name of the DPU port";
				key "PORT_NAME";

				leaf PORT_NAME {
					description "Name of the DPU port";
					type string {
						pattern "[a-z]+[0-9]+";
					}
				}

				leaf state {
					description "Admin state of DPU device";
					type stypes:admin_status;
				}

				leaf vip_ipv4 {
					description "VIP IPv4 address from minigraph";
					type inet:ipv4-address;
				}

				leaf vip_ipv6 {
					description "VIP IPv6 address from minigraph";
					type inet:ipv6-address;
				}

				leaf pa_ipv4 {
					description "PA IPv4 address from minigraph";
					type inet:ipv4-address;
				}

				leaf pa_ipv6 {
					description "PA IPv6 address from minigraph";
					type inet:ipv6-address;
				}

				leaf vdpu_id {
					description "ID of VDPUs from minigraph";
					type string;
				}

				leaf gnmi_port {
					description "Port gNMI runs on.";
					type inet:port-number;
				}
			}
		}
		/* end of container DPU_PORT */
	}
	/* end of container sonic-smart-switch */
}
/* end of module sonic-smart-switch */
